# All Types ReqIF
All types test fixture

# Specification: Test Document

## so-1: REQ-001
System shall handle all types.
Bold text
- IsApproved: true
- DueDate: 2024-12-31T00:00:00+00:00
- Priority: Medium
- Effort: 42
- Confidence: 95.5
- DependsOn -> so-2

### so-3: REQ-003

## so-2: REQ-002
Another requirement.
